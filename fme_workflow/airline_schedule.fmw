FME workspace airline_schedule.fmw

Parameters:
- SourceDataset_CSV2 = C:\Users\Prasa\Documents\PROJECTS (C)\P030\airport_details\world-airports.csv   # Source CSV (Comma Separated Value) File(s)
- SourceDataset_GEOJSON_54 = C:\Users\Prasa\Documents\PROJECTS (C)\P030\airport_details\EUCountries_Airports.geojson   # Source GeoJSON File or URL

Readers:
- CSV2_1: CSV2 from $(SourceDataset_CSV2) in LL-WGS84
- GEOJSON_1: GEOJSON from $(SourceDataset_GEOJSON_54) in LL-WGS84

EUCountries_Airports (reader GEOJSON_1)
    attributes: id int, _id string, name string, icaoCode string, type int, trafficType{} int, magneticDeclination float, country string, elevation.value int, elevation.unit int, elevation.referenceDatum int, ppr boolean, private boolean, skydiveActivity boolean, winchOnly boolean, frequencies{}.value string, frequencies{}.unit int, frequencies{}.type int, frequencies{}.name string, frequencies{}.primary boolean, frequencies{}.publicUse boolean, frequencies{}._id string, runways{}.designator string, runways{}.trueHeading int, runways{}.alignedTrueNorth boolean, runways{}.operations int, runways{}.mainRunway boolean, runways{}.turnDirection int, runways{}.takeOffOnly boolean, runways{}.landingOnly boolean,
      runways{}.surface.composition{} int, runways{}.surface.mainComposite int, runways{}.surface.condition int, runways{}.surface.pcn string, runways{}.dimension.length.value int, runways{}.dimension.length.unit int, runways{}.dimension.width.value int, runways{}.dimension.width.unit int, runways{}.declaredDistance.tora.value int, runways{}.declaredDistance.tora.unit int, runways{}.declaredDistance.lda.value int, runways{}.declaredDistance.lda.unit int, runways{}.pilotCtrlLighting boolean, runways{}.visualApproachAids{} int, runways{}._id string, createdAt string, updatedAt string, createdBy string, updatedBy string, elevationGeoid.geoidHeight float, elevationGeoid.hae float, iataCode string, services.fuelTypes{} int, remarks string, runways{}.surface.mtow.value float, runways{}.surface.mtow.unit int, runways{}.declaredDistance.toda.value int, runways{}.declaredDistance.toda.unit int, runways{}.declaredDistance.asda.value int, runways{}.declaredDistance.asda.unit int,
      runways{}.lightingSystem{} int, contact string, services.handlingFacilities{} int, services.passengerFacilities{} int, runways{}.remarks string, runways{}.exclusiveAircraftType{} int, services.gliderTowing{} int, hoursOfOperation.remarks string, runways{}.instrumentApproachAids{}.identifier string, runways{}.instrumentApproachAids{}.frequency.value string, runways{}.instrumentApproachAids{}.frequency.unit int, runways{}.instrumentApproachAids{}.alignedTrueNorth boolean, runways{}.instrumentApproachAids{}.type int, runways{}.instrumentApproachAids{}.hoursOfOperation.operatingHours{}.dayOfWeek int, runways{}.instrumentApproachAids{}.hoursOfOperation.operatingHours{}.startTime string, runways{}.instrumentApproachAids{}.hoursOfOperation.operatingHours{}.endTime string, runways{}.instrumentApproachAids{}.hoursOfOperation.operatingHours{}.byNotam boolean, runways{}.instrumentApproachAids{}.hoursOfOperation.operatingHours{}.sunrise boolean, runways{}.instrumentApproachAids{}.hoursOfOperation.operatingHours{}.sunset boolean, runways{}.instrumentApproachAids{}.hoursOfOperation.operatingHours{}.publicHolidaysExcluded boolean, runways{}.thresholdLocation.geometry.type string, runways{}.thresholdLocation.geometry.coordinates{} float, runways{}.thresholdLocation.elevation.value int, runways{}.thresholdLocation.elevation.unit int, runways{}.thresholdLocation.elevation.referenceDatum int, images{}.filename string, images{}._id string, runways{}.instrumentApproachAids{}.channel string, runways{}.instrumentApproachAids{}.remarks string, frequencies{}.remarks string,
      hoursOfOperation.operatingHours{}.dayOfWeek int, hoursOfOperation.operatingHours{}.startTime string, hoursOfOperation.operatingHours{}.endTime string, hoursOfOperation.operatingHours{}.byNotam boolean, hoursOfOperation.operatingHours{}.sunrise boolean, hoursOfOperation.operatingHours{}.sunset boolean, hoursOfOperation.operatingHours{}.publicHolidaysExcluded boolean
    -> Tester
Tester
    BOOL_OP = OR
    COMPOSITE_TEST = 1
    TEST_CLAUSE = CASE_INSENSITIVE_TEST iataCode NOT_ATTRIBUTE_IS_MISSING ""
    TEST_MODE = CASE_INSENSITIVE_TEST
    PASSED -> AttributeRemover
AttributeRemover
    REMOVE_ATTRS = _id,createdAt,createdBy,elevation.referenceDatum,elevation.unit,elevation.value,elevationGeoid.geoidHeight,elevationGeoid.hae,frequencies{0}._id,frequencies{0}.name,frequencies{0}.primary,frequencies{0}.publicUse,frequencies{0}.type,frequencies{0}.unit,frequencies{0}.value,icaoCode,id,magneticDeclination,ppr,private,runways{0}._id,runways{0}.alignedTrueNorth,runways{0}.declaredDistance.lda.unit,runways{0}.declaredDistance.lda.value,runways{0}.declaredDistance.tora.unit,runways{0}.declaredDistance.tora.value,runways{0}.designator,runways{0}.dimension.length.unit,runways{0}.dimension.length.value,runways{0}.dimension.width.unit,runways{0}.dimension.width.value,runways{0}.landingOnly,runways{0}.mainRunway,runways{0}.operations,runways{0}.pilotCtrlLighting,runways{0}.surface.composition{0},runways{0}.surface.condition,runways{0}.surface.mainComposite,runways{0}.surface.pcn,runways{0}.takeOffOnly,runways{0}.trueHeading,runways{0}.turnDirection,runways{0}.visualApproachAids{0},services.fuelTypes{0},skydiveActivity,trafficType{0},type,updatedAt,updatedBy,winchOnly,runways{0}.surface.mtow.unit,runways{0}.surface.mtow.value,contact,hoursOfOperation.remarks,runways{0}.declaredDistance.asda.unit,runways{0}.declaredDistance.asda.value,runways{0}.declaredDistance.toda.unit,runways{0}.declaredDistance.toda.value,runways{0}.instrumentApproachAids{0}.alignedTrueNorth,runways{0}.instrumentApproachAids{0}.frequency.unit,runways{0}.instrumentApproachAids{0}.frequency.value,runways{0}.instrumentApproachAids{0}.hoursOfOperation.operatingHours{0}.byNotam,runways{0}.instrumentApproachAids{0}.hoursOfOperation.operatingHours{0}.dayOfWeek,runways{0}.instrumentApproachAids{0}.hoursOfOperation.operatingHours{0}.endTime,runways{0}.instrumentApproachAids{0}.hoursOfOperation.operatingHours{0}.publicHolidaysExcluded,runways{0}.instrumentApproachAids{0}.hoursOfOperation.operatingHours{0}.startTime,runways{0}.instrumentApproachAids{0}.hoursOfOperation.operatingHours{0}.sunrise,runways{0}.instrumentApproachAids{0}.hoursOfOperation.operatingHours{0}.sunset,runways{0}.instrumentApproachAids{0}.identifier,runways{0}.instrumentApproachAids{0}.remarks,runways{0}.instrumentApproachAids{0}.type,runways{0}.lightingSystem{0},services.handlingFacilities{0},services.passengerFacilities{0},remarks,runways{0}.exclusiveAircraftType{0},runways{0}.remarks,services.gliderTowing{0}
    -> AttributeManager
    -> AttributeManager_2
AttributeManager
    ATTR_TABLE = SET_TO api_url = https://aviation-edge.com/v2/public/timetable?key=b4ab65-0a1460&iataCode=@Value(iataCode)&type=departure
    -> HTTPCaller
HTTPCaller
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = @Value(api_url)
    TRANSFER_TIMEOUT_LENGTH = 90
    USE_COOKIES = No
    VERIFY_SSL_CERTIFICATES = Yes
    -> AttributeRemover_4
    <REJECTED> -> Logger
Logger
    LOG_FEATURE = LOG_ONLY
    MAXCOORDS = 20
    MAXFEATS = 20
    MESSAGE = Feature is:
    SEVERITY = INFO
    LOGGED -> DateTimeStamper_2
AttributeManager_2
    ATTR_TABLE = SET_TO api_url = https://aviation-edge.com/v2/public/timetable?key=b4ab65-0a1460&iataCode=@Value(iataCode)&type=arrival
    -> HTTPCaller_2
HTTPCaller_2
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = @Value(api_url)
    TRANSFER_TIMEOUT_LENGTH = 90
    USE_COOKIES = No
    VERIFY_SSL_CERTIFICATES = Yes
    -> AttributeRemover_4
    <REJECTED> -> Logger_2
AttributeRemover_4
    REMOVE_ATTRS = _http_status_code,api_url,frequencies{0}._id,frequencies{0}.name,frequencies{0}.primary,frequencies{0}.publicUse,frequencies{0}.type,frequencies{0}.unit,frequencies{0}.value,runways{0}._id,runways{0}.alignedTrueNorth,runways{0}.declaredDistance.lda.unit,runways{0}.declaredDistance.lda.value,runways{0}.declaredDistance.tora.unit,runways{0}.declaredDistance.tora.value,runways{0}.designator,runways{0}.dimension.length.unit,runways{0}.dimension.length.value,runways{0}.dimension.width.unit,runways{0}.dimension.width.value,runways{0}.landingOnly,runways{0}.mainRunway,runways{0}.operations,runways{0}.pilotCtrlLighting,runways{0}.surface.composition{0},runways{0}.surface.condition,runways{0}.surface.mainComposite,runways{0}.takeOffOnly,runways{0}.trueHeading,runways{0}.turnDirection
    -> Tester_9
Tester_9
    BOOL_OP = OR
    COMPOSITE_TEST = 1
    TEST_CLAUSE = CASE_INSENSITIVE_TEST @Value(_response_body) NOT_CONTAINS {"error":"No Record Found","success":false}
    TEST_MODE = TEST
    PASSED -> JSONFragmenter_2
JSONFragmenter_2
    EXPLODE_FORMAT = JSON
    EXTRACT_ATTR = No
    JSON_ATTR = _response_body
    JSON_QUERY = json[*]
    READ_FROM_FILE = NO
    REJECT_EMPTY_LISTS = YES
    FRAGMENTS -> JSONFlattener_2
JSONFlattener_2
    ERROR_LIST_ATTR = _json_error
    JSON_DOCUMENT = @Value(_response_body)
    NEW_ATTRIBUTES = airline.iataCode airline.icaoCode airline.name flight.iataNumber flight.icaoNumber arrival.iataCode arrival.icaoCode arrival.scheduledTime arrival.estimatedTime arrival.delay arrival.terminal arrival.gate arrival.baggage codeshared.airline.iataCode codeshared.airline.name codeshared.flight.iataNumber departure.iataCode departure.icaoCode departure.scheduledTime departure.estimatedTime departure.delay departure.terminal departure.gate departure.baggage status type
    READ_FROM_FILE = NO
    RECURSIVE = Yes
    -> Tester_10
Tester_10
    BOOL_OP = OR
    COMPOSITE_TEST = 1
    TEST_CLAUSE = TEST codeshared.airline.iataCode ATTRIBUTE_IS_MISSING ""
    TEST_MODE = TEST
    PASSED -> FeatureJoiner_2 [LEFT]
Logger_2
    LOG_FEATURE = LOG_ONLY
    MAXCOORDS = 20
    MAXFEATS = 20
    MESSAGE = Feature is:
    SEVERITY = INFO
    LOGGED -> DateTimeStamper_2
DateTimeStamper_2
    DATETIME_ATTR = _timestamp
    INCLUDE_OFFSET = NO
    STAMP_TYPE = datetime
    TIMEZONE = local
    -> DateTimeConverter_2
DateTimeConverter_2
    DATETIME_ATTR = _timestamp
    OUT_FORMAT = %Y%m%d%H
    PASSTHROUGH = NO
    REPAIR_INPUT = YES
    -> AttributeCreator_2
AttributeCreator_2
    ATTR_TABLE = SET_TO output_fileName = C:\Users\Prasa\Documents\PROJECTS (C)\P030\output_files\error_log_@Value(_timestamp).json
    -> FeatureWriter_2 [Output]
FeatureWriter_2
    COORDSYS = LL-WGS84
    DATASET = @Value(output_fileName)
    DATASET_ATTR = _dataset
    FEATURE_TYPE_LIST_ATTR = _feature_type
    FORMAT = JSON
    JSON_COORDINATE_SYSTEM_FORMAT = OGC-WKT
    JSON_COORDINATE_SYSTEM_KEY = json_ogc_wkt_crs
    JSON_DESTINATION_DATASETTYPE_VALIDATION = Yes
    JSON_FEATURE_TYPE_KEY = json_featuretype
    JSON_GEOMETRY_FORMAT = GeoJSON
    JSON_GEOMETRY_KEY = json_geometry
    JSON_INDENT_SIZE = 0
    JSON_MAX_COORDINATE_PRECISION = 10
    JSON_PRETTY_PRINT = YES
    JSON_WRITER_CHARSET = UTF-8
    JSON_WRITE_BOM = No
    JSON_WRITE_COORDINATE_SYSTEM = YES
    JSON_WRITE_FEATURE_TYPE_KEY = YES
    JSON_WRITE_GEOMETRY = YES
    TOTAL_FEATURES_WRITTEN_ATTR = _total_features_written
CSV (reader CSV2_1)
    attributes: id uint32, ident string, type string, name string, latitude_deg y_coordinate, longitude_deg x_coordinate, elevation_ft z_coordinate, continent string, country_name string, iso_country string, region_name string, iso_region string, local_region string, municipality string, scheduled_service uint8, gps_code string, icao_code string, iata_code string, local_code string, home_link string, wikipedia_link string, keywords string, score uint32, last_updated string
    -> AttributeRemover_3
AttributeRemover_3
    REMOVE_ATTRS = elevation_ft,home_link,id,ident,local_code,local_region,municipality,region_name,scheduled_service,score,type,wikipedia_link,gps_code,iso_country,iso_region,keywords,last_updated,icao_code
    -> AttributeRenamer
AttributeRenamer
    ATTR_TABLE = RENAME_SET_DEFAULT name > airport_name
    -> FeatureJoiner_2 [RIGHT]
    -> FeatureJoiner [RIGHT]
FeatureJoiner_2
    ATTR_CONFLICT_RES = Use Left
    GEOMETRY_HANDLING = Use Left
    JOIN_KEYS = arrival.iataCode iata_code AUTO
    JOIN_MODE = Left
    JOINED -> AttributeRemover_5
AttributeRemover_5
    REMOVE_ATTRS = _response_body,codeshared.airline.iataCode,codeshared.airline.name,codeshared.flight.iataNumber,frequencies{0}._id,frequencies{0}.name,frequencies{0}.primary,frequencies{0}.publicUse,frequencies{0}.type,frequencies{0}.unit,frequencies{0}.value,iataCode,json_index,json_type,runways{0}._id,runways{0}.alignedTrueNorth,runways{0}.declaredDistance.asda.unit,runways{0}.declaredDistance.asda.value,runways{0}.declaredDistance.lda.unit,runways{0}.declaredDistance.lda.value,runways{0}.declaredDistance.toda.unit,runways{0}.declaredDistance.toda.value,runways{0}.declaredDistance.tora.unit,runways{0}.declaredDistance.tora.value,runways{0}.designator,runways{0}.dimension.length.unit,runways{0}.dimension.length.value,runways{0}.dimension.width.unit,runways{0}.dimension.width.value,runways{0}.landingOnly,runways{0}.mainRunway,runways{0}.operations,runways{0}.pilotCtrlLighting,runways{0}.surface.composition{0},runways{0}.surface.condition,runways{0}.surface.mainComposite,runways{0}.surface.pcn,runways{0}.takeOffOnly,runways{0}.trueHeading,runways{0}.turnDirection,runways{0}.visualApproachAids{0},services.fuelTypes{0},services.handlingFacilities{0},services.passengerFacilities{0},trafficType{0},name,iata_code
    -> AttributeRenamer_2
AttributeRenamer_2
    ATTR_TABLE:
      RENAME_SET_DEFAULT name > airport_name
      RENAME_SET_DEFAULT airline.iataCode > airline_iataCode
      RENAME_SET_DEFAULT airline.icaoCode > airline_icaoCode
      RENAME_SET_DEFAULT airline.name > airline_name
      RENAME_SET_DEFAULT airport_name > arrival_airportName
      RENAME_SET_DEFAULT arrival.baggage > arrival_baggage
      RENAME_SET_DEFAULT arrival.delay > arrival_delay
      RENAME_SET_DEFAULT arrival.estimatedTime > arrival_estimatedTime
      RENAME_SET_DEFAULT arrival.gate > arrival_gate
      RENAME_SET_DEFAULT arrival.iataCode > arrival_iataCode
      RENAME_SET_DEFAULT arrival.icaoCode > arrival_icaoCode
      RENAME_SET_DEFAULT arrival.scheduledTime > arrival_scheduledTime
      RENAME_SET_DEFAULT arrival.terminal > arrival_terminal
      RENAME_SET_DEFAULT continent > arrival_continent
      RENAME_SET_DEFAULT country_name > arrival_country
      RENAME_SET_DEFAULT departure.baggage > departure_baggage
      RENAME_SET_DEFAULT departure.delay > departure_delay
      RENAME_SET_DEFAULT departure.estimatedTime > departure_estimatedTime
      RENAME_SET_DEFAULT departure.gate > departure_gate
      RENAME_SET_DEFAULT departure.iataCode > departure_iataCode
      RENAME_SET_DEFAULT departure.icaoCode > departure_icaoCode
      RENAME_SET_DEFAULT departure.scheduledTime > departure_scheduledTime
      RENAME_SET_DEFAULT departure.terminal > departure_terminal
      RENAME_SET_DEFAULT flight.iataNumber > flight_iataNumber
      RENAME_SET_DEFAULT flight.icaoNumber > flight_icaoNumber
      RENAME_SET_DEFAULT latitude_deg > arrival_airport_latitude
      RENAME_SET_DEFAULT longitude_deg > arrival_airport_longitude
    -> FeatureJoiner [LEFT]
FeatureJoiner
    ATTR_CONFLICT_RES = Use Left
    GEOMETRY_HANDLING = Use Left
    JOIN_KEYS = departure_iataCode iata_code AUTO
    JOIN_MODE = Left
    JOINED -> AttributeRemover_6
AttributeRemover_6
    REMOVE_ATTRS = _response_body,codeshared.airline.iataCode,codeshared.airline.name,codeshared.flight.iataNumber,frequencies{0}._id,frequencies{0}.name,frequencies{0}.primary,frequencies{0}.publicUse,frequencies{0}.type,frequencies{0}.unit,frequencies{0}.value,iataCode,json_index,json_type,runways{0}._id,runways{0}.alignedTrueNorth,runways{0}.declaredDistance.asda.unit,runways{0}.declaredDistance.asda.value,runways{0}.declaredDistance.lda.unit,runways{0}.declaredDistance.lda.value,runways{0}.declaredDistance.toda.unit,runways{0}.declaredDistance.toda.value,runways{0}.declaredDistance.tora.unit,runways{0}.declaredDistance.tora.value,runways{0}.designator,runways{0}.dimension.length.unit,runways{0}.dimension.length.value,runways{0}.dimension.width.unit,runways{0}.dimension.width.value,runways{0}.landingOnly,runways{0}.mainRunway,runways{0}.operations,runways{0}.pilotCtrlLighting,runways{0}.surface.composition{0},runways{0}.surface.condition,runways{0}.surface.mainComposite,runways{0}.surface.pcn,runways{0}.takeOffOnly,runways{0}.trueHeading,runways{0}.turnDirection,runways{0}.visualApproachAids{0},services.fuelTypes{0},services.handlingFacilities{0},services.passengerFacilities{0},trafficType{0},name,iata_code
    -> AttributeRenamer_3
AttributeRenamer_3
    ATTR_TABLE:
      RENAME_SET_DEFAULT continent > departure_continent
      RENAME_SET_DEFAULT country_name > departure_country
      RENAME_SET_DEFAULT airport_name > departure_airportName
      RENAME_SET_DEFAULT latitude_deg > departure_airport_latitude
      RENAME_SET_DEFAULT longitude_deg > departure_airport_longitude
      RENAME_SET_DEFAULT country > country_code
    -> DateTimeStamper
DateTimeStamper
    DATETIME_ATTR = _timestamp
    INCLUDE_OFFSET = NO
    STAMP_TYPE = datetime
    TIMEZONE = local
    -> DateTimeConverter
DateTimeConverter
    DATETIME_ATTR = _timestamp
    OUT_FORMAT = %Y%m%d%H
    PASSTHROUGH = NO
    REPAIR_INPUT = YES
    -> AttributeCreator
AttributeCreator
    ATTR_TABLE = SET_TO output_fileName = C:\Users\Prasa\Documents\PROJECTS (C)\P030\output_files\@Value(_timestamp).geojson
    -> FeatureWriter [Output]
FeatureWriter
    COORDSYS = LL-WGS84
    DATASET = @Value(output_fileName)
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_INDENT_SIZE = 0
    GEOJSON_MAX_COORDINATE_PRECISION = 10
    GEOJSON_PRETTY_PRINT = YES
    GEOJSON_STRICT_SPEC = Yes
    GEOJSON_WGS84_REPROJECTION = Yes
    GEOJSON_WRITER_CHARSET = UTF-8
    GEOJSON_WRITE_BOM = No
    TOTAL_FEATURES_WRITTEN_ATTR = _total_features_written
